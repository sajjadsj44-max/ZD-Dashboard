;; Two revisions of one drawing, for the takeoff's duplicates (OVERKILL) and DWG compare tests, in inches (INSUNITS 1).
;; Revision 1 is saved as zd_rev1_2018.dwg, edited in the same session (every object keeps its handle, as in an architect's
;; next revision) and saved as zd_rev2_2018.dwg. ZDOUT (the folder, with a trailing /) is set by the script that loads this.
;;   accoreconsole /s run.scr   — run.scr: (setq ZDOUT "C:/…/") (load "…/make_zd_revs.lsp") then _.QUIT _Y
(setvar "CMDECHO" 0)
(setvar "INSUNITS" 1) (setvar "LUNITS" 4) (setvar "MEASUREMENT" 0) (setvar "OSMODE" 0)
(defun mklayer (nm col)
  (if (not (tblsearch "LAYER" nm))
    (entmake (list '(0 . "LAYER") '(100 . "AcDbSymbolTableRecord") '(100 . "AcDbLayerTableRecord") (cons 2 nm) '(70 . 0) (cons 62 col) '(6 . "Continuous")))))
(mklayer "WALL" 1) (mklayer "FLOOR" 3) (mklayer "DOOR" 2) (mklayer "TEXT" 7)
(defun ln (lay a b) (entmake (list '(0 . "LINE") (cons 8 lay) (cons 10 a) (cons 11 b))) (entlast))
(defun pl (lay pts)
  (entmake (append (list '(0 . "LWPOLYLINE") '(100 . "AcDbEntity") (cons 8 lay) '(100 . "AcDbPolyline") (cons 90 (length pts)) '(70 . 1))
                   (mapcar '(lambda (p) (cons 10 p)) pts)))
  (entlast))
;; walls: a 20' x 10' outline (60 ft); its bottom line copied in place, its right line drawn again the other way round (duplicates)
(setq wA (ln "WALL" '(0.0 0.0 0.0) '(240.0 0.0 0.0))
      wB (ln "WALL" '(240.0 0.0 0.0) '(240.0 120.0 0.0))
      wC (ln "WALL" '(240.0 120.0 0.0) '(0.0 120.0 0.0))
      wD (ln "WALL" '(0.0 120.0 0.0) '(0.0 0.0 0.0)))
(ln "WALL" '(0.0 0.0 0.0) '(240.0 0.0 0.0))
(ln "WALL" '(240.0 120.0 0.0) '(240.0 0.0 0.0))
;; floors: 10' x 12' (120 Sft) twice on one spot, and 8' x 8' (64 Sft)
(setq f1 (pl "FLOOR" '((300.0 0.0) (420.0 0.0) (420.0 144.0) (300.0 144.0))))
(pl "FLOOR" '((300.0 0.0) (420.0 0.0) (420.0 144.0) (300.0 144.0)))
(setq f2 (pl "FLOOR" '((450.0 0.0) (546.0 0.0) (546.0 96.0) (450.0 96.0))))
;; a door block D1 (3'-0" leaf and swing) inserted twice, the first one twice on one spot
(entmake '((0 . "BLOCK") (2 . "D1") (70 . 0) (10 0.0 0.0 0.0)))
(entmake '((0 . "LINE") (8 . "0") (10 0.0 0.0 0.0) (11 0.0 36.0 0.0)))
(entmake '((0 . "ARC") (8 . "0") (10 0.0 0.0 0.0) (40 . 36.0) (50 . 0.0) (51 . 1.5707963267948966)))
(entmake '((0 . "ENDBLK")))
(defun door (p) (entmake (list '(0 . "INSERT") '(8 . "DOOR") '(2 . "D1") (cons 10 p) '(41 . 1.0) '(42 . 1.0) '(43 . 1.0) '(50 . 0.0))) (entlast))
(door '(30.0 0.0 0.0)) (door '(30.0 0.0 0.0)) (door '(150.0 0.0 0.0))
(entmake '((0 . "TEXT") (8 . "TEXT") (10 100.0 60.0 0.0) (40 . 6.0) (1 . "ROOM 1")))
(setq tx (entlast))
(command "._ZOOM" "_E")
(command "._SAVEAS" "2018" (strcat ZDOUT "zd_rev1_2018.dwg"))
;; the next revision: the top wall taken out, a 10' wall and a door added, the small floor moved 2' right, the room renamed
(entdel wC)
(ln "WALL" '(0.0 200.0 0.0) '(120.0 200.0 0.0))
(door '(90.0 120.0 0.0))
(command "._MOVE" f2 "" "_non" '(0.0 0.0 0.0) "_non" '(24.0 0.0 0.0))
(setq e (entget tx))
(entmod (subst '(1 . "ROOM 1A") (assoc 1 e) e))
(command "._ZOOM" "_E")
(command "._SAVEAS" "2018" (strcat ZDOUT "zd_rev2_2018.dwg"))
(princ "\nREVISIONS MADE\n")
