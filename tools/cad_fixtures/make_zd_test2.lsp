;; Second test drawing: the harder entity cases. Units millimetres (INSUNITS 4), so the metric path is tested too.
(setvar "CMDECHO" 1) (setvar "INSUNITS" 4) (setvar "MEASUREMENT" 1) (setvar "LTSCALE" 100.0) (setvar "PLINETYPE" 0)
(defun lay (nm col) (if (not (tblsearch "LAYER" nm)) (entmake (list '(0 . "LAYER") '(100 . "AcDbSymbolTableRecord") '(100 . "AcDbLayerTableRecord") (cons 2 nm) '(70 . 0) (cons 62 col) '(6 . "Continuous")))))
(lay "S-COL" 4) (lay "A-ANNO" 2) (lay "A-EQPM" 30)
(setq BS (chr 92))
;; a block with an attribute, a layer-0 ByBlock part and a part on its own layer, nested inside another block
(entmake '((0 . "BLOCK") (2 . "COLTAG") (70 . 2) (10 0.0 0.0 0.0)))
(entmake '((0 . "CIRCLE") (8 . "0") (62 . 0) (10 0.0 0.0 0.0) (40 . 300.0)))
(entmake '((0 . "LINE") (8 . "S-COL") (10 -300.0 0.0 0.0) (11 300.0 0.0 0.0)))
(entmake '((0 . "ATTDEF") (8 . "0") (10 -100.0 -400.0 0.0) (40 . 150.0) (1 . "C1") (3 . "Column mark") (2 . "MARK") (70 . 0)))
(entmake '((0 . "ENDBLK")))
(entmake '((0 . "BLOCK") (2 . "COLGRP") (70 . 0) (10 0.0 0.0 0.0)))
(entmake '((0 . "INSERT") (8 . "0") (2 . "COLTAG") (10 0.0 0.0 0.0) (41 . 1.0) (42 . 1.0) (43 . 1.0)))
(entmake '((0 . "INSERT") (8 . "0") (2 . "COLTAG") (10 2000.0 0.0 0.0) (41 . 1.0) (42 . 1.0) (43 . 1.0)))
(entmake '((0 . "ENDBLK")))
;; COLTAG inserted with its attribute, red (ByBlock parts follow), and the group nested
(setvar "ATTREQ" 1) (setvar "ATTDIA" 0)
(setvar "CLAYER" "S-COL")
(command "._-INSERT" "COLTAG" "_non" '(0.0 6000.0) 1.0 1.0 0.0 "C7")
(command "._CHPROP" (entlast) "" "_C" "1" "")
(command "._-INSERT" "COLGRP" "_non" '(4000.0 6000.0) 1.0 1.0 0.0)
;; a mirrored copy (extrusion 0,0,-1) and a non-uniformly scaled one (the circle becomes an ellipse)
(command "._MIRROR" (entlast) "" "_non" '(8000.0 0.0) "_non" '(8000.0 1000.0) "_N")
(command "._-INSERT" "COLTAG" "_non" '(12000.0 6000.0) 2.0 1.0 30.0 "C9")
;; heavy 2D polyline with a bulge and a wide lightweight polyline
(setvar "CLAYER" "A-EQPM")
(command "._PLINE" "_non" '(0.0 0.0) "_non" '(3000.0 0.0) "_A" "_non" '(3000.0 2000.0) "_L" "_non" '(0.0 2000.0) "_C")
(setvar "PLINETYPE" 2)
(command "._PLINE" "_non" '(4000.0 0.0) "_W" 100.0 100.0 "_non" '(7000.0 0.0) "_non" '(7000.0 2000.0) "") (setvar "PLINEWID" 0.0)
;; text in every alignment, rotated text, and MTEXT with paragraphs and formatting
(setvar "CLAYER" "A-ANNO")
(command "._-STYLE" "ZDTXT" "Arial" 0.0 0.8 0.0 "_N" "_N")
(foreach J '(("_L" 0.0) ("_C" 1000.0) ("_R" 2000.0) ("_M" 3000.0) ("_TL" 4000.0) ("_BR" 5000.0))
  (command "._-TEXT" "_J" (car J) "_non" (list (cadr J) -2000.0) 200.0 0.0 (strcat "AL" (car J))))
(command "._-TEXT" "_non" '(6000.0 -2000.0) 200.0 45.0 "ROT45")
(entmake (list '(0 . "MTEXT") '(100 . "AcDbEntity") '(8 . "A-ANNO") '(100 . "AcDbMText") '(10 0.0 -4000.0 0.0) '(40 . 150.0) '(41 . 3000.0) '(71 . 1)
  (cons 1 (strcat "FIRST LINE" BS "PSECOND " BS "fArial|b1;BOLD" BS "f; 1" BS "S1/2; IN" BS "PTHIRD %%c50 %%d %%p5"))))
;; hatch with an island (circle in a rectangle), a gradient hatch, and a hatch bounded by an arc
(setvar "CLAYER" "0")
(command "._RECTANG" "_non" '(0.0 -8000.0) "_non" '(3000.0 -6000.0)) (setq r1 (entlast))
(command "._CIRCLE" "_non" '(1500.0 -7000.0) 500.0) (setq c1 (entlast))
(command "._-HATCH" "_P" "ANSI37" 50.0 0.0 "_S" r1 c1 "" "")
(command "._RECTANG" "_non" '(4000.0 -8000.0) "_non" '(7000.0 -6000.0))
(command "._-HATCH" "_P" "_S" "_S" (entlast) "" "")
(command "._PLINE" "_non" '(8000.0 -8000.0) "_W" 0.0 0.0 "_non" '(11000.0 -8000.0) "_A" "_non" '(11000.0 -6000.0) "_L" "_non" '(8000.0 -6000.0) "_C") (setq a1 (entlast))
(command "._-HATCH" "_P" "_S" "_S" a1 "" "")
(command "._CHPROP" (entlast) "" "_C" "_T" "200,100,50" "")
;; dimensions: aligned, radius, diameter, angular; a leader and a multileader
(setvar "CLAYER" "A-ANNO") (setvar "DIMSCALE" 50.0)
(command "._DIMALIGNED" "_non" '(0.0 0.0) "_non" '(3000.0 0.0) "_non" '(1500.0 -600.0))
(command "._CIRCLE" "_non" '(14000.0 0.0) 1000.0) (setq cc (entlast))
(command "._DIMRADIUS" (list cc '(15000.0 0.0 0.0)) "_non" '(15500.0 500.0))
(command "._DIMDIAMETER" (list cc '(13000.0 0.0 0.0)) "_non" '(12000.0 -800.0))
(command "._LINE" "_non" '(17000.0 0.0) "_non" '(20000.0 0.0) "") (setq l1 (entlast))
(command "._LINE" "_non" '(17000.0 0.0) "_non" '(19000.0 2000.0) "") (setq l2 (entlast))
(command "._DIMANGULAR" (list l1 '(20000.0 0.0 0.0)) (list l2 '(19000.0 2000.0 0.0)) "_non" '(19500.0 1200.0))
(command "._LEADER" "_non" '(0.0 3000.0) "_non" '(1000.0 4000.0) "_non" '(2000.0 4000.0) "" "LEADER NOTE" "")
(command "._MLEADER" "_non" '(4000.0 3000.0) "_non" '(5000.0 4000.0) "MLEADER NOTE")
;; xline, ray, 2D solid, 3D face, true-colour line
(command "._XLINE" "_non" '(0.0 10000.0) "_non" '(1000.0 10000.0) "")
(command "._RAY" "_non" '(0.0 11000.0) "_non" '(1000.0 11500.0) "")
(command "._SOLID" "_non" '(22000.0 0.0) "_non" '(23000.0 0.0) "_non" '(22000.0 1000.0) "_non" '(23000.0 1000.0) "")
(command "._3DFACE" "_non" '(24000.0 0.0) "_non" '(25000.0 0.0) "_non" '(25000.0 1000.0) "_non" '(24000.0 1000.0) "")
(entmake '((0 . "LINE") (8 . "0") (420 . 3381759) (10 22000.0 3000.0 0.0) (11 25000.0 3000.0 0.0)))
;; MINSERT 2 x 3
(command "._MINSERT" "COLTAG" "_non" '(0.0 14000.0) 1.0 1.0 0.0 2 3 2000.0 1500.0 "C11")
(command "._ZOOM" "_E")
(princ "\nTEST DRAWING 2 MADE\n")
